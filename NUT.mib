NUT-MIB DEFINITIONS ::= BEGIN

IMPORTS
        MODULE-IDENTITY, OBJECT-TYPE, Integer32, enterprises
            FROM SNMPv2-SMI

        DisplayString, TEXTUAL-CONVENTION
            FROM SNMPv2-TC
        MODULE-COMPLIANCE, OBJECT-GROUP
            FROM SNMPv2-CONF;

nutMIB MODULE-IDENTITY
    LAST-UPDATED "201206110000Z"
    ORGANIZATION "Network UPS Tools"
    CONTACT-INFO
              "        Luiz Angelo Daros de Luca
                       E-mail: luizluca@gmail.com"
    DESCRIPTION
               "The MIB module list information about local configured UPS
	       managed by NUT."
    REVISION     "201206110000Z"
    DESCRIPTION  "First release"
       ::= { enterprises 26376 99 }

-- temporary usage of tresc number as NUT does not have one
tresc OBJECT IDENTIFIER ::= { enterprises 26376 }

NutDeviceIndexType ::= TEXTUAL-CONVENTION
    DISPLAY-HINT "d"
    STATUS       current
    DESCRIPTION
            "A unique value, greater than zero, for each device. It is
	    recommended that values are assigned contiguously starting
            from 1." 
    SYNTAX       Integer32 (1..2147483647)

NutOutletIndexType ::= TEXTUAL-CONVENTION
    DISPLAY-HINT "d"
    STATUS       current
    DESCRIPTION
            "A unique value, greater than or equal to zero, for each outlet. It is
	    recommended that values are assigned contiguously starting
            from 1." 
    SYNTAX       Integer32 (0..2147483647)

TenthInteger32 ::=  TEXTUAL-CONVENTION
    DISPLAY-HINT    "d-1"
    STATUS          current
    DESCRIPTION
       "A Integer32 that represents a real number, with one decimal case. I.e.: 123 for 12.3"
    SYNTAX          Integer32

HundredthInteger32 ::=  TEXTUAL-CONVENTION
    DISPLAY-HINT    "d-2"
    STATUS          current
    DESCRIPTION
       "A Integer32 that represents a real number, with two decimal case. I.e.: 123 for 1.23"
    SYNTAX          Integer32     
    
nutMIBObjects        OBJECT IDENTIFIER ::= { nutMIB 1 }

--
-- This are information from device.* ups.* variables plus the ups name and desc,
-- which are not part of the variables but returned by the command "upsc -L"
--

nutDeviceTable     OBJECT-TYPE
    SYNTAX      SEQUENCE OF NutDeviceEntryType
    MAX-ACCESS      not-accessible
    STATUS          current
    DESCRIPTION
         "A list of device."
    ::= { nutMIBObjects 1 }

NutDeviceEntryType ::=
	SEQUENCE {
		nutDeviceIndex	NutDeviceIndexType,
		nutDeviceName	DisplayString,
		nutDeviceDesc	DisplayString,
		nutDeviceModel	DisplayString,
		nutDeviceMfr	DisplayString,
		nutDeviceSerial	DisplayString,
		nutDeviceType	DisplayString
	}

nutDeviceEntry OBJECT-TYPE
    SYNTAX      NutDeviceEntryType
    MAX-ACCESS  not-accessible
    STATUS      current
    DESCRIPTION
            "An entry containing information about a particular device."
    INDEX   { nutDeviceIndex }
    ::= { nutDeviceTable 1 }

nutDeviceIndex OBJECT-TYPE
	SYNTAX      NutDeviceIndexType
	MAX-ACCESS  not-accessible
	STATUS      current
	DESCRIPTION
            "A unique value, greater than zero, for each device"
    ::= { nutDeviceEntry 1 }

nutDeviceName OBJECT-TYPE
    SYNTAX      DisplayString (SIZE (0..255))
    MAX-ACCESS  read-only
    STATUS      current
    DESCRIPTION
            "The name of the device."
    ::= { nutDeviceEntry 2 }

nutDeviceDesc OBJECT-TYPE
    SYNTAX      DisplayString (SIZE (0..255))
    MAX-ACCESS  read-only
    STATUS      current
    DESCRIPTION
            "A textual string containing information about the device."
    ::= { nutDeviceEntry 3 }

-- Name                           Description                                                            Example value
-- device.model                   Device model                                                           BladeUPS  
-- device.mfr                     Device manufacturer                                                    Eaton     
-- device.serial                  Device serial number (opaque string)                                   WS9643050926
-- device.type                    Device type (ups, pdu, scd)                                            ups       

nutDeviceModel OBJECT-TYPE
    SYNTAX      DisplayString (SIZE (0..255))
    MAX-ACCESS  read-only
    STATUS      current
    DESCRIPTION
        "Device model. I.e. BladeUPS."
    ::= { nutDeviceEntry 4 }

nutDeviceMfr OBJECT-TYPE
    SYNTAX      DisplayString (SIZE (0..255))
    MAX-ACCESS  read-only
    STATUS      current
    DESCRIPTION
        "Device manufacturer. I.e. Eaton."
    ::= { nutDeviceEntry 5 }

nutDeviceSerial OBJECT-TYPE
    SYNTAX      DisplayString (SIZE (0..255))
    MAX-ACCESS  read-only
    STATUS      current
    DESCRIPTION
        "Device serial number (opaque string). I.e. WS9643050926."
    ::= { nutDeviceEntry 6 }

nutDeviceType OBJECT-TYPE
    SYNTAX      DisplayString (SIZE (0..255))
    MAX-ACCESS  read-only
    STATUS      current
    DESCRIPTION
        "Device type (ups, pdu, scd). I.e. ups."
    ::= { nutDeviceEntry 7 }

-- Name                           Description                                                            Example value
-- ups.status                     UPS status                                                             OL        
-- ups.alarm                      UPS alarms                                                             OVERHEAT  
-- ups.time                       Internal UPS clock time (opaque string)                                12:34     
-- ups.date                       Internal UPS clock date (opaque string)                                01-02-03  
-- ups.model                      UPS model                                                              SMART-UPS 700
-- ups.mfr                        UPS manufacturer                                                       APC       
-- ups.mfr.date                   UPS manufacturing date (opaque string)                                 10/17/96  
-- ups.serial                     UPS serial number (opaque string)                                      WS9643050926
-- ups.vendorid                   Vendor ID for USB devices                                              0463      
-- ups.productid                  Product ID for USB devices                                             0001      
-- ups.firmware                   UPS firmware (opaque string)                                           50.9.D    
-- ups.firmware.aux               Auxiliary device firmware                                              4Kx       
-- ups.temperature                UPS temperature (degrees C)                                            042.7     
-- ups.load                       Load on UPS (percent)                                                  023.4     
-- ups.load.high                  Load when UPS switches to overload condition ("OVER") (percent)        100       
-- ups.id                         UPS system identifier (opaque string)                                  Sierra    
-- ups.delay.start                Interval to wait before restarting the load (seconds)                  0         
-- ups.delay.reboot               Interval to wait before rebooting the UPS (seconds)                    60        
-- ups.delay.shutdown             Interval to wait after shutdown with delay command (seconds)           20        
-- ups.timer.start                Time before the load will be started (seconds)                         30        
-- ups.timer.reboot               Time before the load will be rebooted (seconds)                        10        
-- ups.timer.shutdown             Time before the load will be shutdown (seconds)                        20        
-- ups.test.interval              Interval between self tests (seconds)                                  1209600 (two weeks)
-- ups.test.result                Results of last self test (opaque string)                              Bad battery pack
-- ups.display.language           Language to use on front panel (* opaque)                              E         
-- ups.contacts                   UPS external contact sensors (* opaque)                                F0        
-- ups.efficiency                 Efficiency of the UPS (ratio of the output current on the input current) (percent) 95        
-- ups.power                      Current value of apparent power (Volt-Amps)                            500       
-- ups.power.nominal              Nominal value of apparent power (Volt-Amps)                            500       
-- ups.realpower                  Current value of real power (Watts)                                    300       
-- ups.realpower.nominal          Nominal value of real power (Watts)                                    300       
-- ups.beeper.status              UPS beeper status (enabled, disabled or muted)                         enabled   
-- ups.type                       UPS type (* opaque)                                                    offline   
-- ups.watchdog.status            UPS watchdog status (enabled or disabled)                              disabled  
-- ups.start.auto                 UPS starts when mains is (re)applied                                   yes       
-- ups.start.battery              Allow to start UPS from battery                                        yes       
-- ups.start.reboot               UPS coldstarts from battery (enabled or disabled)                      yes       

nutUpsTable     OBJECT-TYPE
    SYNTAX      SEQUENCE OF NutUpsEntryType
    MAX-ACCESS      not-accessible
    STATUS          current
    DESCRIPTION
         "A list of ups."
    ::= { nutMIBObjects 2 }

NutUpsEntryType ::=
    SEQUENCE {
       nutUpsStatus DisplayString,
       nutUpsAlarm DisplayString,
       nutUpsTime DisplayString,
       nutUpsDate DisplayString,
       nutUpsModel DisplayString,
       nutUpsMfr DisplayString,
       nutUpsMfrDate DisplayString,
       nutUpsSerial DisplayString,
       nutUpsVendorid DisplayString,
       nutUpsProductid DisplayString,
       nutUpsFirmware DisplayString,
       nutUpsFirmwareAux DisplayString,
       nutUpsTemperature TenthInteger32,
       nutUpsLoad Integer32,
       nutUpsLoadHigh Integer32,
       nutUpsId DisplayString,
       nutUpsDelayStart Integer32, 
       nutUpsDelayReboot Integer32,
       nutUpsDelayShutdown Integer32,
       nutUpsTimerStart Integer32,
       nutUpsTimerReboot Integer32,
       nutUpsTimerShutdown Integer32,
       nutUpsTestInterval Integer32,
       nutUpsTestResult DisplayString,
       nutUpsDisplayLanguage DisplayString,
       nutUpsContacts DisplayString,
       nutUpsEfficiency Integer32,
       nutUpsPower Integer32,
       nutUpsPowerNominal Integer32,
       nutUpsRealpower Integer32,
       nutUpsRealpowerNominal Integer32,
       nutUpsBeeperStatus DisplayString,
       nutUpsType DisplayString,
       nutUpsWatchdogStatus DisplayString,
       nutUpsStartAuto INTEGER,
       nutUpsStartBattery INTEGER,
       nutUpsStartReboot INTEGER
    }

nutUpsEntry OBJECT-TYPE
    SYNTAX      NutUpsEntryType
    MAX-ACCESS  not-accessible
    STATUS      current
    DESCRIPTION
            "An entry containing information about a particular ups."
    INDEX   { nutDeviceIndex }
    ::= { nutUpsTable 1 }

nutUpsStatus OBJECT-TYPE
    SYNTAX      DisplayString (SIZE (0..255))
    MAX-ACCESS  read-only
    STATUS      current
    DESCRIPTION
        "UPS status. I.e. OL."
    ::= { nutUpsEntry 1 }

nutUpsAlarm OBJECT-TYPE
    SYNTAX      DisplayString (SIZE (0..255))
    MAX-ACCESS  read-only
    STATUS      current
    DESCRIPTION
        "UPS alarms. I.e. OVERHEAT."
    ::= { nutUpsEntry 2 }

nutUpsTime OBJECT-TYPE
    SYNTAX      DisplayString (SIZE (0..255))
    MAX-ACCESS  read-only
    STATUS      current
    DESCRIPTION
        "Internal UPS clock time (opaque string). I.e. 12:34."
    ::= { nutUpsEntry 3 }

nutUpsDate OBJECT-TYPE
    SYNTAX      DisplayString (SIZE (0..255))
    MAX-ACCESS  read-only
    STATUS      current
    DESCRIPTION
        "Internal UPS clock date (opaque string). I.e. 01-02-03."
    ::= { nutUpsEntry 4 }

nutUpsModel OBJECT-TYPE
    SYNTAX      DisplayString (SIZE (0..255))
    MAX-ACCESS  read-only
    STATUS      current
    DESCRIPTION
        "UPS model. I.e. SMART-UPS 700."
    ::= { nutUpsEntry 5 }

nutUpsMfr OBJECT-TYPE
    SYNTAX      DisplayString (SIZE (0..255))
    MAX-ACCESS  read-only
    STATUS      current
    DESCRIPTION
        "UPS manufacturer. I.e. APC."
    ::= { nutUpsEntry 6 }

nutUpsMfrDate OBJECT-TYPE
    SYNTAX      DisplayString (SIZE (0..255))
    MAX-ACCESS  read-only
    STATUS      current
    DESCRIPTION
        "UPS manufacturing date (opaque string). I.e. 10/17/96."
    ::= { nutUpsEntry 7 }

nutUpsSerial OBJECT-TYPE
    SYNTAX      DisplayString (SIZE (0..255))
    MAX-ACCESS  read-only
    STATUS      current
    DESCRIPTION
        "UPS serial number (opaque string). I.e. WS9643050926."
    ::= { nutUpsEntry 8 }

nutUpsVendorid OBJECT-TYPE
    SYNTAX      DisplayString (SIZE (0..255))
    MAX-ACCESS  read-only
    STATUS      current
    DESCRIPTION
        "Vendor ID for USB devices. I.e. 0463."
    ::= { nutUpsEntry 9 }

nutUpsProductid OBJECT-TYPE
    SYNTAX      DisplayString (SIZE (0..255))
    MAX-ACCESS  read-only
    STATUS      current
    DESCRIPTION
        "Product ID for USB devices. I.e. 0001."
    ::= { nutUpsEntry 10 }

nutUpsFirmware OBJECT-TYPE
    SYNTAX      DisplayString (SIZE (0..255))
    MAX-ACCESS  read-only
    STATUS      current
    DESCRIPTION
        "UPS firmware (opaque string). I.e. 50.9.D."
    ::= { nutUpsEntry 11 }

nutUpsFirmwareAux OBJECT-TYPE
    SYNTAX      DisplayString (SIZE (0..255))
    MAX-ACCESS  read-only
    STATUS      current
    DESCRIPTION
        "Auxiliary device firmware. I.e. 4Kx."
    ::= { nutUpsEntry 12 }

nutUpsTemperature OBJECT-TYPE
    SYNTAX      TenthInteger32 (-2730..2147483647)
    MAX-ACCESS  read-only
    STATUS      current
    DESCRIPTION
        "UPS temperature (in 0.1 degrees C). I.e. 427 (for 42.7oC)."
    ::= { nutUpsEntry 13 }

nutUpsLoad OBJECT-TYPE
    SYNTAX      Integer32 (0..100)
    MAX-ACCESS  read-only
    STATUS      current
    DESCRIPTION
        "Load on UPS (percent). I.e. 023."
    ::= { nutUpsEntry 14 }

nutUpsLoadHigh OBJECT-TYPE
    SYNTAX      Integer32 (0..100)
    MAX-ACCESS  read-only
    STATUS      current
    DESCRIPTION
        "Load when UPS switches to overload condition ('OVER') (percent). I.e. 100."
    ::= { nutUpsEntry 15 }

nutUpsId OBJECT-TYPE
    SYNTAX      DisplayString (SIZE (0..255))
    MAX-ACCESS  read-only
    STATUS      current
    DESCRIPTION
        "UPS system identifier (opaque string). I.e. Sierra."
    ::= { nutUpsEntry 16 }

nutUpsDelayStart OBJECT-TYPE
    SYNTAX      Integer32 (-1..2147483647)
    MAX-ACCESS  read-only
    STATUS      current
    DESCRIPTION
        "Interval to wait before restarting the load (seconds). I.e. 0."
    ::= { nutUpsEntry 17 }

nutUpsDelayReboot OBJECT-TYPE
    SYNTAX      Integer32 (-1..2147483647)
    MAX-ACCESS  read-only
    STATUS      current
    DESCRIPTION
        "Interval to wait before rebooting the UPS (seconds). I.e. 60."
    ::= { nutUpsEntry 18 }

nutUpsDelayShutdown OBJECT-TYPE
    SYNTAX      Integer32 (-1..2147483647)
    MAX-ACCESS  read-only
    STATUS      current
    DESCRIPTION
        "Interval to wait after shutdown with delay command (seconds). I.e. 20."
    ::= { nutUpsEntry 19 }

nutUpsTimerStart OBJECT-TYPE
    SYNTAX      Integer32 (-1..2147483647)
    MAX-ACCESS  read-only
    STATUS      current
    DESCRIPTION
        "Time before the load will be started (seconds). I.e. 30."
    ::= { nutUpsEntry 20 }

nutUpsTimerReboot OBJECT-TYPE
    SYNTAX      Integer32 (-1..2147483647)
    MAX-ACCESS  read-only
    STATUS      current
    DESCRIPTION
        "Time before the load will be rebooted (seconds). I.e. 10."
    ::= { nutUpsEntry 21 }

nutUpsTimerShutdown OBJECT-TYPE
    SYNTAX      Integer32 (-1..2147483647)
    MAX-ACCESS  read-only
    STATUS      current
    DESCRIPTION
        "Time before the load will be shutdown (seconds). I.e. 20."
    ::= { nutUpsEntry 22 }

nutUpsTestInterval OBJECT-TYPE
    SYNTAX      Integer32 (-1..2147483647)
    MAX-ACCESS  read-only
    STATUS      current
    DESCRIPTION
        "Interval between self tests (seconds). I.e. 1209600 (two weeks)."
    ::= { nutUpsEntry 23 }

nutUpsTestResult OBJECT-TYPE
    SYNTAX      DisplayString (SIZE (0..255))
    MAX-ACCESS  read-only
    STATUS      current
    DESCRIPTION
        "Results of last self test (opaque string). I.e. Bad battery pack."
    ::= { nutUpsEntry 24 }

nutUpsDisplayLanguage OBJECT-TYPE
    SYNTAX      DisplayString (SIZE (0..255))
    MAX-ACCESS  read-only
    STATUS      current
    DESCRIPTION
        "Language to use on front panel (* opaque). I.e. E."
    ::= { nutUpsEntry 25 }

nutUpsContacts OBJECT-TYPE
    SYNTAX      DisplayString (SIZE (0..255))
    MAX-ACCESS  read-only
    STATUS      current
    DESCRIPTION
        "UPS external contact sensors (* opaque). I.e. F0."
    ::= { nutUpsEntry 26 }

nutUpsEfficiency OBJECT-TYPE
    SYNTAX      Integer32 (0..100)
    MAX-ACCESS  read-only
    STATUS      current
    DESCRIPTION
        "Efficiency of the UPS (ratio of the output current on the input current) (percent). I.e. 95."
    ::= { nutUpsEntry 27 }

nutUpsPower OBJECT-TYPE
    SYNTAX      Integer32 (0..2147483647)
    MAX-ACCESS  read-only
    STATUS      current
    DESCRIPTION
        "Current value of apparent power (Volt-Amps). I.e. 500."
    ::= { nutUpsEntry 28 }

nutUpsPowerNominal OBJECT-TYPE
    SYNTAX      Integer32 (0..2147483647)
    MAX-ACCESS  read-only
    STATUS      current
    DESCRIPTION
        "Nominal value of apparent power (Volt-Amps). I.e. 500."
    ::= { nutUpsEntry 29 }

nutUpsRealpower OBJECT-TYPE
    SYNTAX      Integer32 (0..2147483647)
    MAX-ACCESS  read-only
    STATUS      current
    DESCRIPTION
        "Current value of real power (Watts). I.e. 300."
    ::= { nutUpsEntry 30 }

nutUpsRealpowerNominal OBJECT-TYPE
    SYNTAX      Integer32 (0..2147483647)
    MAX-ACCESS  read-only
    STATUS      current
    DESCRIPTION
        "Nominal value of real power (Watts). I.e. 300."
    ::= { nutUpsEntry 31 }

nutUpsBeeperStatus OBJECT-TYPE
    SYNTAX      DisplayString (SIZE (0..255))
    MAX-ACCESS  read-only
    STATUS      current
    DESCRIPTION
        "UPS beeper status (enabled, disabled or muted). I.e. enabled."
    ::= { nutUpsEntry 32 }

nutUpsType OBJECT-TYPE
    SYNTAX      DisplayString (SIZE (0..255))
    MAX-ACCESS  read-only
    STATUS      current
    DESCRIPTION
        "UPS type (* opaque). I.e. offline."
    ::= { nutUpsEntry 33 }

nutUpsWatchdogStatus OBJECT-TYPE
    SYNTAX      DisplayString (SIZE (0..255))
    MAX-ACCESS  read-only
    STATUS      current
    DESCRIPTION
        "UPS watchdog status (enabled or disabled). I.e. disabled."
    ::= { nutUpsEntry 34 }

nutUpsStartAuto OBJECT-TYPE
    SYNTAX      INTEGER { no(0), yes(1) }
    MAX-ACCESS  read-only
    STATUS      current
    DESCRIPTION
        "UPS starts when mains is (re)applied. I.e. yes."
    ::= { nutUpsEntry 35 }

nutUpsStartBattery OBJECT-TYPE
    SYNTAX      INTEGER { no(0), yes(1) }
    MAX-ACCESS  read-only
    STATUS      current
    DESCRIPTION
        "Allow to start UPS from battery. I.e. yes."
    ::= { nutUpsEntry 36 }

nutUpsStartReboot OBJECT-TYPE
    SYNTAX      INTEGER { no(0), yes(1) }
    MAX-ACCESS  read-only
    STATUS      current
    DESCRIPTION
        "UPS coldstarts from battery (enabled or disabled). I.e. yes."
    ::= { nutUpsEntry 37 }

-- Name                           Description                                                            Example value
-- input.voltage                  Input voltage                                                          121.5     
-- input.voltage.maximum          Maximum incoming voltage seen                                          130       
-- input.voltage.minimum          Minimum incoming voltage seen                                          100       
-- input.voltage.nominal          Nominal input voltage                                                  120       
-- input.voltage.extended         Extended input voltage range                                           no        
-- input.transfer.reason          Reason for last transfer to battery (* opaque)                         T         
-- input.transfer.low             Low voltage transfer point                                             91        
-- input.transfer.high            High voltage transfer point                                            132       
-- input.transfer.low.min         smallest settable low voltage transfer point                           85        
-- input.transfer.low.max         greatest settable low voltage transfer point                           95        
-- input.transfer.high.min        smallest settable high voltage transfer point                          131       
-- input.transfer.high.max        greatest settable high voltage transfer point                          136       
-- input.sensitivity              Input power sensitivity                                                H (high)  
-- input.quality                  Input power quality (* opaque)                                         FF        
-- input.current                  Input current (A)                                                      4.25      
-- input.current.nominal          Nominal input current (A)                                              5.0       
-- input.frequency                Input line frequency (Hz)                                              60.00     
-- input.frequency.nominal        Nominal input line frequency (Hz)                                      60        
-- input.frequency.low            Input line frequency low (Hz)                                          47        
-- input.frequency.high           Input line frequency high (Hz)                                         63        
-- input.frequency.extended       Extended input frequency range                                         no        
-- input.transfer.boost.low       Low voltage boosting transfer point                                    190       
-- input.transfer.boost.high      High voltage boosting transfer point                                   210       
-- input.transfer.trim.low        Low voltage trimming transfer point                                    230       
-- input.transfer.trim.high       High voltage trimming transfer point                                   240
--
-- input.phases                   (3 for three-phase, absent or 1 for 1 phase)                           1

nutInputTable     OBJECT-TYPE
    SYNTAX      SEQUENCE OF NutInputEntryType
    MAX-ACCESS      not-accessible
    STATUS          current
    DESCRIPTION
         "A list of input."
    ::= { nutMIBObjects 3 }

NutInputEntryType ::=
    SEQUENCE {
       nutInputVoltage TenthInteger32,
       nutInputVoltageMaximum TenthInteger32,
       nutInputVoltageMinimum TenthInteger32,
       nutInputVoltageNominal TenthInteger32,
       nutInputVoltageExtended INTEGER,
       nutInputTransferReason DisplayString,
       nutInputTransferLow Integer32,
       nutInputTransferHigh Integer32,
       nutInputTransferLowMin Integer32, 
       nutInputTransferLowMax Integer32,
       nutInputTransferHighMin Integer32,
       nutInputTransferHighMax Integer32,
       nutInputSensitivity DisplayString,
       nutInputQuality DisplayString,
       nutInputCurrent HundredthInteger32,
       nutInputCurrentNominal HundredthInteger32,
       nutInputFrequency TenthInteger32,
       nutInputFrequencyNominal TenthInteger32,
       nutInputFrequencyLow TenthInteger32,
       nutInputFrequencyHigh TenthInteger32,
       nutInputFrequencyExtended INTEGER,
       nutInputTransferBoostLow Integer32,
       nutInputTransferBoostHigh Integer32,
       nutInputTransferTrimLow Integer32,
       nutInputTransferTrimHigh Integer32,
       nutInputPhases Integer32
    }

nutInputEntry OBJECT-TYPE
    SYNTAX      NutInputEntryType
    MAX-ACCESS  not-accessible
    STATUS      current
    DESCRIPTION
            "An entry containing information about a particular input."
    INDEX   { nutDeviceIndex }
    ::= { nutInputTable 1 }

nutInputVoltage OBJECT-TYPE
    SYNTAX      TenthInteger32 (0..2147483647) 
    MAX-ACCESS  read-only
    STATUS      current
    DESCRIPTION
        "Input voltage (0.1V). I.e. 1212 (121.2V)."
    ::= { nutInputEntry 1 }

nutInputVoltageMaximum OBJECT-TYPE
    SYNTAX      TenthInteger32 (0..2147483647)
    MAX-ACCESS  read-only
    STATUS      current
    DESCRIPTION
        "Maximum incoming voltage seen (0.1V). I.e. 1300."
    ::= { nutInputEntry 2 }

nutInputVoltageMinimum OBJECT-TYPE
    SYNTAX      TenthInteger32 (0..2147483647)
    MAX-ACCESS  read-only
    STATUS      current
    DESCRIPTION
        "Minimum incoming voltage seen (0.1V). I.e. 1000."
    ::= { nutInputEntry 3 }

nutInputVoltageNominal OBJECT-TYPE
    SYNTAX      TenthInteger32 (0..2147483647)
    MAX-ACCESS  read-only
    STATUS      current
    DESCRIPTION
        "Nominal input voltage (0.1V). I.e. 1200."
    ::= { nutInputEntry 4 }

nutInputVoltageExtended OBJECT-TYPE
    SYNTAX      INTEGER { no(0), yes(1) }
    MAX-ACCESS  read-only
    STATUS      current
    DESCRIPTION
        "Extended input voltage range. I.e. no."
    ::= { nutInputEntry 5 }

nutInputTransferReason OBJECT-TYPE
    SYNTAX      DisplayString (SIZE (0..255))
    MAX-ACCESS  read-only
    STATUS      current
    DESCRIPTION
        "Reason for last transfer to battery (* opaque). I.e. T."
    ::= { nutInputEntry 6 }

nutInputTransferLow OBJECT-TYPE
    SYNTAX      Integer32 (0..2147483647)
    MAX-ACCESS  read-only
    STATUS      current
    DESCRIPTION
        "Low voltage transfer point. I.e. 91."
    ::= { nutInputEntry 7 }

nutInputTransferHigh OBJECT-TYPE
    SYNTAX      Integer32 (0..2147483647)
    MAX-ACCESS  read-only
    STATUS      current
    DESCRIPTION
        "High voltage transfer point. I.e. 132."
    ::= { nutInputEntry 8 }

nutInputTransferLowMin OBJECT-TYPE
    SYNTAX      Integer32 (0..2147483647) 
    MAX-ACCESS  read-only
    STATUS      current
    DESCRIPTION
        "smallest settable low voltage transfer point. I.e. 85."
    ::= { nutInputEntry 9 }

nutInputTransferLowMax OBJECT-TYPE
    SYNTAX      Integer32 (0..2147483647)
    MAX-ACCESS  read-only
    STATUS      current
    DESCRIPTION
        "greatest settable low voltage transfer point. I.e. 95."
    ::= { nutInputEntry 10 }

nutInputTransferHighMin OBJECT-TYPE
    SYNTAX      Integer32 (0..2147483647)
    MAX-ACCESS  read-only
    STATUS      current
    DESCRIPTION
        "smallest settable high voltage transfer point. I.e. 131."
    ::= { nutInputEntry 11 }

nutInputTransferHighMax OBJECT-TYPE
    SYNTAX      Integer32 (0..2147483647)
    MAX-ACCESS  read-only
    STATUS      current
    DESCRIPTION
        "greatest settable high voltage transfer point. I.e. 136."
    ::= { nutInputEntry 12 }

nutInputSensitivity OBJECT-TYPE
    SYNTAX      DisplayString (SIZE (0..255))
    MAX-ACCESS  read-only
    STATUS      current
    DESCRIPTION
        "Input power sensitivity. I.e. H (high)."
    ::= { nutInputEntry 13 }

nutInputQuality OBJECT-TYPE
    SYNTAX      DisplayString (SIZE (0..255))
    MAX-ACCESS  read-only
    STATUS      current
    DESCRIPTION
        "Input power quality (* opaque). I.e. FF."
    ::= { nutInputEntry 14 }

nutInputCurrent OBJECT-TYPE
    SYNTAX      HundredthInteger32 (0..2147483647)
    MAX-ACCESS  read-only
    STATUS      current
    DESCRIPTION
        "Input current (0.01 A). I.e. 425 (4.25A)."
    ::= { nutInputEntry 15 }

nutInputCurrentNominal OBJECT-TYPE
    SYNTAX      HundredthInteger32 (0..2147483647)
    MAX-ACCESS  read-only
    STATUS      current
    DESCRIPTION
        "Nominal input current (0.01 A). I.e. 500 (5 A)."
    ::= { nutInputEntry 16 }

nutInputFrequency OBJECT-TYPE
    SYNTAX      TenthInteger32 (0..2147483647)
    MAX-ACCESS  read-only
    STATUS      current
    DESCRIPTION
        "Input line frequency (0.1 Hz). I.e. 602 (60.2 Hz)."
    ::= { nutInputEntry 17 }

nutInputFrequencyNominal OBJECT-TYPE
    SYNTAX      TenthInteger32 (0..2147483647)
    MAX-ACCESS  read-only
    STATUS      current
    DESCRIPTION
        "Nominal input line frequency (0.1 Hz). I.e. 600."
    ::= { nutInputEntry 18 }

nutInputFrequencyLow OBJECT-TYPE
    SYNTAX      TenthInteger32 (0..2147483647)
    MAX-ACCESS  read-only
    STATUS      current
    DESCRIPTION
        "Input line frequency low (0.1 Hz). I.e. 470."
    ::= { nutInputEntry 19 }

nutInputFrequencyHigh OBJECT-TYPE
    SYNTAX      TenthInteger32 (0..2147483647)
    MAX-ACCESS  read-only
    STATUS      current
    DESCRIPTION
        "Input line frequency high (0.1 Hz). I.e. 630."
    ::= { nutInputEntry 20 }

nutInputFrequencyExtended OBJECT-TYPE
    SYNTAX      INTEGER { no(0), yes(1) }
    MAX-ACCESS  read-only
    STATUS      current
    DESCRIPTION
        "Extended input frequency range. I.e. no."
    ::= { nutInputEntry 21 }

nutInputTransferBoostLow OBJECT-TYPE
    SYNTAX      Integer32 (0..2147483647)
    MAX-ACCESS  read-only
    STATUS      current
    DESCRIPTION
        "Low voltage boosting transfer point. I.e. 190."
    ::= { nutInputEntry 22 }

nutInputTransferBoostHigh OBJECT-TYPE
    SYNTAX      Integer32 (0..2147483647)
    MAX-ACCESS  read-only
    STATUS      current
    DESCRIPTION
        "High voltage boosting transfer point. I.e. 210."
    ::= { nutInputEntry 23 }

nutInputTransferTrimLow OBJECT-TYPE
    SYNTAX      Integer32 (0..2147483647)
    MAX-ACCESS  read-only
    STATUS      current
    DESCRIPTION
        "Low voltage trimming transfer point. I.e. 230."
    ::= { nutInputEntry 24 }

nutInputTransferTrimHigh OBJECT-TYPE
    SYNTAX      Integer32 (0..2147483647)
    MAX-ACCESS  read-only
    STATUS      current
    DESCRIPTION
        "High voltage trimming transfer point. I.e. 240."
    ::= { nutInputEntry 25 }

nutInputPhases OBJECT-TYPE
    SYNTAX      Integer32 (1|3)
    MAX-ACCESS  read-only
    STATUS      current
    DESCRIPTION
        "(3 for three-phase, absent or 1 for 1 phase). I.e. 3"
    ::= { nutInputEntry 26 }
    
-- Name                           Description                                                            Example value
-- output.voltage                 Output voltage (V)                                                     120.9     
-- output.voltage.nominal         Nominal output voltage (V)                                             120       
-- output.frequency               Output frequency (Hz)                                                  59.9      
-- output.frequency.nominal       Nominal output frequency (Hz)                                          60        
-- output.current                 Output current (A)                                                     4.25      
-- output.current.nominal         Nominal output current (A)                                             5.0       
--
-- output.phases                  (3 for three-phase, absent or 1 for 1 phase)                           1

nutOutputTable     OBJECT-TYPE
    SYNTAX      SEQUENCE OF NutOutputEntryType
    MAX-ACCESS      not-accessible
    STATUS          current
    DESCRIPTION
         "A list of output."
    ::= { nutMIBObjects 4 }

NutOutputEntryType ::=
    SEQUENCE {
       nutOutputVoltage TenthInteger32,
       nutOutputVoltageNominal TenthInteger32,
       nutOutputFrequency TenthInteger32,
       nutOutputFrequencyNominal TenthInteger32,
       nutOutputCurrent HundredthInteger32,
       nutOutputCurrentNominal HundredthInteger32,
       nutOutputPhases Integer32
    }

nutOutputEntry OBJECT-TYPE
    SYNTAX      NutOutputEntryType
    MAX-ACCESS  not-accessible
    STATUS      current
    DESCRIPTION
            "An entry containing information about a particular output."
    INDEX   { nutDeviceIndex }
    ::= { nutOutputTable 1 }

nutOutputVoltage OBJECT-TYPE
    SYNTAX      TenthInteger32 (0..2147483647)
    MAX-ACCESS  read-only
    STATUS      current
    DESCRIPTION
        "Output voltage (0.1 V). I.e. 120.9."
    ::= { nutOutputEntry 1 }

nutOutputVoltageNominal OBJECT-TYPE
    SYNTAX      TenthInteger32 (0..2147483647)
    MAX-ACCESS  read-only
    STATUS      current
    DESCRIPTION
        "Nominal output voltage (0.1 V). I.e. 120."
    ::= { nutOutputEntry 2 }

nutOutputFrequency OBJECT-TYPE
    SYNTAX      TenthInteger32 (0..2147483647)
    MAX-ACCESS  read-only
    STATUS      current
    DESCRIPTION
        "Output frequency (0.1 Hz). I.e. 599 (59.9 Hz)."
    ::= { nutOutputEntry 3 }

nutOutputFrequencyNominal OBJECT-TYPE
    SYNTAX      TenthInteger32 (0..2147483647)
    MAX-ACCESS  read-only
    STATUS      current
    DESCRIPTION
        "Nominal output frequency (0.1 Hz). I.e. 60."
    ::= { nutOutputEntry 4 }

nutOutputCurrent OBJECT-TYPE
    SYNTAX      HundredthInteger32 (0..2147483647)
    MAX-ACCESS  read-only
    STATUS      current
    DESCRIPTION
        "Output current (0.01 A). I.e. 425 (42.5 A)."
    ::= { nutOutputEntry 5 }

nutOutputCurrentNominal OBJECT-TYPE
    SYNTAX      HundredthInteger32 (0..2147483647)
    MAX-ACCESS  read-only
    STATUS      current
    DESCRIPTION
        "Nominal output current (0.01 A). I.e. 500 (5 A)."
    ::= { nutOutputEntry 6 }
    
nutOutputPhases OBJECT-TYPE
    SYNTAX      Integer32 (1|3)
    MAX-ACCESS  read-only
    STATUS      current
    DESCRIPTION
        "(3 for three-phase, absent or 1 for 1 phase). I.e. 3"
    ::= { nutOutputEntry 7 }    

-- Name                           Description                                                            Example value
-- battery.charge                 Battery charge (percent)                                               100.0     
-- battery.charge.low             Remaining battery level when UPS switches to LB (percent)              20        
-- battery.charge.restart         Minimum battery level for UPS restart after power-off                  20        
-- battery.charge.warning         Battery level when UPS switches to "Warning" state (percent)           50        
-- battery.voltage                Battery voltage (V)                                                    24.84     
-- battery.capacity               Battery capacity (Ah)                                                  7.2       
-- battery.current                Battery current (A)                                                    1.19      
-- battery.temperature            Battery temperature (degrees C)                                        050.7     
-- battery.voltage.nominal        Nominal battery voltage (V)                                            024       
-- battery.runtime                Battery runtime (seconds) Remaining battery runtime                    1080      
-- battery.runtime.low            when UPS switches to LB (seconds)                                      180       
-- battery.alarm.threshold        Battery alarm threshold                                                0 (immediate)
-- battery.date                   Battery change date (opaque string)                                    11/14/00  
-- battery.mfr.date               Battery manufacturing date (opaque string)                             2005/04/02
-- battery.packs                  Number of battery packs                                                001       
-- battery.packs.bad              Number of bad battery packs                                            000       
-- battery.type                   Battery chemistry (opaque string)                                      PbAc      
-- battery.protection             Prevent deep discharge of battery                                      yes       
-- battery.energysave             Switch off when running on battery and no/low load                     no        

nutBatteryTable     OBJECT-TYPE
    SYNTAX      SEQUENCE OF NutBatteryEntryType
    MAX-ACCESS      not-accessible
    STATUS          current
    DESCRIPTION
         "A list of battery."
    ::= { nutMIBObjects 5 }

NutBatteryEntryType ::=
    SEQUENCE {
       nutBatteryCharge TenthInteger32,
       nutBatteryChargeLow TenthInteger32,
       nutBatteryChargeRestart TenthInteger32,
       nutBatteryChargeWarning TenthInteger32,
       nutBatteryVoltage HundredthInteger32,
       nutBatteryCapacity TenthInteger32,
       nutBatteryCurrent HundredthInteger32,
       nutBatteryTemperature TenthInteger32,
       nutBatteryVoltageNominal HundredthInteger32,
       nutBatteryRuntime Integer32,
       nutBatteryRuntimeLow Integer32,
       nutBatteryAlarmThreshold Integer32,
       nutBatteryDate DisplayString,
       nutBatteryMfrDate DisplayString,
       nutBatteryPacks Integer32,
       nutBatteryPacksBad Integer32,
       nutBatteryType DisplayString,
       nutBatteryProtection INTEGER,
       nutBatteryEnergysave INTEGER
    }

nutBatteryEntry OBJECT-TYPE
    SYNTAX      NutBatteryEntryType
    MAX-ACCESS  not-accessible
    STATUS      current
    DESCRIPTION
            "An entry containing information about a particular battery."
    INDEX   { nutDeviceIndex }
    ::= { nutBatteryTable 1 }

nutBatteryCharge OBJECT-TYPE
    SYNTAX      TenthInteger32 (0..1000)
    MAX-ACCESS  read-only
    STATUS      current
    DESCRIPTION
        "Battery charge (0.1 percent). I.e. 1000 (100%)."
    ::= { nutBatteryEntry 1 }

nutBatteryChargeLow OBJECT-TYPE
    SYNTAX      TenthInteger32 (0..1000)
    MAX-ACCESS  read-only
    STATUS      current
    DESCRIPTION
        "Remaining battery level when UPS switches to LB (0.1 percent). I.e. 20."
    ::= { nutBatteryEntry 2 }

nutBatteryChargeRestart OBJECT-TYPE
    SYNTAX      TenthInteger32 (0..1000)
    MAX-ACCESS  read-only
    STATUS      current
    DESCRIPTION
        "Minimum battery level for UPS restart after power-off (0.1 percent). I.e. 20."
    ::= { nutBatteryEntry 3 }

nutBatteryChargeWarning OBJECT-TYPE
    SYNTAX      TenthInteger32 (0..1000)
    MAX-ACCESS  read-only
    STATUS      current
    DESCRIPTION
        "Battery level when UPS switches to 'Warning' state (0.1 percent). I.e. 50."
    ::= { nutBatteryEntry 4 }

nutBatteryVoltage OBJECT-TYPE
    SYNTAX      HundredthInteger32 (0..2147483647)
    MAX-ACCESS  read-only
    STATUS      current
    DESCRIPTION
        "Battery voltage (0.01V). I.e. 2484 (24.84 V)."
    ::= { nutBatteryEntry 5 }

nutBatteryCapacity OBJECT-TYPE
    SYNTAX      TenthInteger32 (0..2147483647)
    MAX-ACCESS  read-only
    STATUS      current
    DESCRIPTION
        "Battery capacity (0.1 Ah). I.e. 72 (7.2 Ah)."
    ::= { nutBatteryEntry 6 }

nutBatteryCurrent OBJECT-TYPE
    SYNTAX      HundredthInteger32 (0..2147483647)
    MAX-ACCESS  read-only
    STATUS      current
    DESCRIPTION
        "Battery current (0.01 A). I.e. 119 (1.19 A)."
    ::= { nutBatteryEntry 7 }

nutBatteryTemperature OBJECT-TYPE
    SYNTAX      TenthInteger32 (-2730..2147483647) 
    MAX-ACCESS  read-only
    STATUS      current
    DESCRIPTION
        "Battery temperature (0.1 degrees C). I.e. 507 (50.7oC)."
    ::= { nutBatteryEntry 8 }

nutBatteryVoltageNominal OBJECT-TYPE
    SYNTAX      HundredthInteger32 (0..2147483647)
    MAX-ACCESS  read-only
    STATUS      current
    DESCRIPTION
        "Nominal battery voltage (0.01 V). I.e. 024."
    ::= { nutBatteryEntry 9 }

nutBatteryRuntime OBJECT-TYPE
    SYNTAX      Integer32 (0..2147483647)
    MAX-ACCESS  read-only
    STATUS      current
    DESCRIPTION
        "Battery runtime (seconds) Remaining battery runtime. I.e. 1080."
    ::= { nutBatteryEntry 10 }

nutBatteryRuntimeLow OBJECT-TYPE
    SYNTAX      Integer32 (0..2147483647)
    MAX-ACCESS  read-only
    STATUS      current
    DESCRIPTION
        "when UPS switches to LB (seconds). I.e. 180."
    ::= { nutBatteryEntry 11 }

nutBatteryAlarmThreshold OBJECT-TYPE
    SYNTAX      Integer32 (0..2147483647)
    MAX-ACCESS  read-only
    STATUS      current
    DESCRIPTION
        "Battery alarm threshold. I.e. 0 (immediate)."
    ::= { nutBatteryEntry 12 }

nutBatteryDate OBJECT-TYPE
    SYNTAX      DisplayString (SIZE (0..255))
    MAX-ACCESS  read-only
    STATUS      current
    DESCRIPTION
        "Battery change date (opaque string). I.e. 11/14/00."
    ::= { nutBatteryEntry 13 }

nutBatteryMfrDate OBJECT-TYPE
    SYNTAX      DisplayString (SIZE (0..255))
    MAX-ACCESS  read-only
    STATUS      current
    DESCRIPTION
        "Battery manufacturing date (opaque string). I.e. 2005/04/02."
    ::= { nutBatteryEntry 14 }

nutBatteryPacks OBJECT-TYPE
    SYNTAX      Integer32 (0..2147483647)
    MAX-ACCESS  read-only
    STATUS      current
    DESCRIPTION
        "Number of battery packs. I.e. 001."
    ::= { nutBatteryEntry 15 }

nutBatteryPacksBad OBJECT-TYPE
    SYNTAX      Integer32 (0..2147483647)
    MAX-ACCESS  read-only
    STATUS      current
    DESCRIPTION
        "Number of bad battery packs. I.e. 000."
    ::= { nutBatteryEntry 16 }

nutBatteryType OBJECT-TYPE
    SYNTAX      DisplayString (SIZE (0..255))
    MAX-ACCESS  read-only
    STATUS      current
    DESCRIPTION
        "Battery chemistry (opaque string). I.e. PbAc."
    ::= { nutBatteryEntry 17 }

nutBatteryProtection OBJECT-TYPE
    SYNTAX      INTEGER { no(0), yes(1) }
    MAX-ACCESS  read-only
    STATUS      current
    DESCRIPTION
        "Prevent deep discharge of battery. I.e. yes."
    ::= { nutBatteryEntry 18 }

nutBatteryEnergysave OBJECT-TYPE
    SYNTAX      INTEGER { no(0), yes(1) }
    MAX-ACCESS  read-only
    STATUS      current
    DESCRIPTION
        "Switch off when running on battery and no/low load. I.e. no."
    ::= { nutBatteryEntry 19 }

-- Name                           Description                                                            Example value
-- ambient.temperature            Ambient temperature (degrees C)                                        25.40     
-- ambient.temperature.alarm      Temperature alarm (enabled/disabled)                                   enabled   
-- ambient.temperature.high       Temperature threshold high (degrees C)                                 40        
-- ambient.temperature.low        Temperature threshold low (degrees C)                                  5         
-- ambient.temperature.maximum    Maximum temperature seen (degrees C)                                   37.6      
-- ambient.temperature.minimum    Minimum temperature seen (degrees C)                                   18.1      
-- ambient.humidity               Ambient relative humidity (percent)                                    038.8     
-- ambient.humidity.alarm         Relative humidity alarm (enabled/disabled)                             enabled   
-- ambient.humidity.high          Relative humidity threshold high (percent)                             80        
-- ambient.humidity.low           Relative humidity threshold high (percent)                             10        
-- ambient.humidity.maximum       Maximum relative humidity seen (percent)                               60        
-- ambient.humidity.minimum       Minimum relative humidity seen (percent)                               13        

nutAmbientTable     OBJECT-TYPE
    SYNTAX      SEQUENCE OF NutAmbientEntryType
    MAX-ACCESS      not-accessible
    STATUS          current
    DESCRIPTION
         "A list of device ambient information."
    ::= { nutMIBObjects 6 }

NutAmbientEntryType ::=
    SEQUENCE {
       nutAmbientTemperature TenthInteger32,
       nutAmbientTemperatureAlarm INTEGER,
       nutAmbientTemperatureHigh TenthInteger32, 
       nutAmbientTemperatureLow TenthInteger32,
       nutAmbientTemperatureMaximum TenthInteger32,
       nutAmbientTemperatureMinimum TenthInteger32,
       nutAmbientHumidity TenthInteger32,
       nutAmbientHumidityAlarm INTEGER,
       nutAmbientHumidityHigh TenthInteger32,
       nutAmbientHumidityLow TenthInteger32,
       nutAmbientHumidityMaximum TenthInteger32,
       nutAmbientHumidityMinimum TenthInteger32
    }

nutAmbientEntry OBJECT-TYPE
    SYNTAX      NutAmbientEntryType
    MAX-ACCESS  not-accessible
    STATUS      current
    DESCRIPTION
            "An entry containing information about a particular ambient."
    INDEX   { nutDeviceIndex }
    ::= { nutAmbientTable 1 }

nutAmbientTemperature OBJECT-TYPE
    SYNTAX      TenthInteger32 (-2730..2147483647)
    MAX-ACCESS  read-only
    STATUS      current
    DESCRIPTION
        "Ambient temperature (0.1 degrees C). I.e. 25.40."
    ::= { nutAmbientEntry 1 }

nutAmbientTemperatureAlarm OBJECT-TYPE
    SYNTAX      INTEGER { disabled(0), enabled(1) }
    MAX-ACCESS  read-only
    STATUS      current
    DESCRIPTION
        "Temperature alarm (enabled/disabled). I.e. enabled."
    ::= { nutAmbientEntry 2 }

nutAmbientTemperatureHigh OBJECT-TYPE
    SYNTAX      TenthInteger32 (-2730..2147483647)
    MAX-ACCESS  read-only
    STATUS      current
    DESCRIPTION
        "Temperature threshold high (degrees C). I.e. 40."
    ::= { nutAmbientEntry 3 }

nutAmbientTemperatureLow OBJECT-TYPE
    SYNTAX      TenthInteger32 (-2730..2147483647)
    MAX-ACCESS  read-only
    STATUS      current
    DESCRIPTION
        "Temperature threshold low (degrees C). I.e. 5."
    ::= { nutAmbientEntry 4 }

nutAmbientTemperatureMaximum OBJECT-TYPE
    SYNTAX      TenthInteger32 (-2730..2147483647)
    MAX-ACCESS  read-only
    STATUS      current
    DESCRIPTION
        "Maximum temperature seen (0.1 degrees C). I.e. 37.6."
    ::= { nutAmbientEntry 5 }

nutAmbientTemperatureMinimum OBJECT-TYPE
    SYNTAX      TenthInteger32 (-2730..2147483647)
    MAX-ACCESS  read-only
    STATUS      current
    DESCRIPTION
        "Minimum temperature seen (0.1 degrees C). I.e. 18.1."
    ::= { nutAmbientEntry 6 }

nutAmbientHumidity OBJECT-TYPE
    SYNTAX      TenthInteger32 (0..1000)
    MAX-ACCESS  read-only
    STATUS      current
    DESCRIPTION
        "Ambient relative humidity (0.1 percent). I.e. 388 (38.8%)."
    ::= { nutAmbientEntry 7 }

nutAmbientHumidityAlarm OBJECT-TYPE
    SYNTAX      INTEGER { disabled(0), enabled(1) }
    MAX-ACCESS  read-only
    STATUS      current
    DESCRIPTION
        "Relative humidity alarm (enabled/disabled). I.e. enabled."
    ::= { nutAmbientEntry 8 }

nutAmbientHumidityHigh OBJECT-TYPE
    SYNTAX      TenthInteger32 (0..1000)
    MAX-ACCESS  read-only
    STATUS      current
    DESCRIPTION
        "Relative humidity threshold high (percent). I.e. 80."
    ::= { nutAmbientEntry 9 }

nutAmbientHumidityLow OBJECT-TYPE
    SYNTAX      TenthInteger32 (0..1000)
    MAX-ACCESS  read-only
    STATUS      current
    DESCRIPTION
        "Relative humidity threshold high (percent). I.e. 10."
    ::= { nutAmbientEntry 10 }

nutAmbientHumidityMaximum OBJECT-TYPE
    SYNTAX      TenthInteger32 (0..1000)
    MAX-ACCESS  read-only
    STATUS      current
    DESCRIPTION
        "Maximum relative humidity seen (percent). I.e. 60."
    ::= { nutAmbientEntry 11 }

nutAmbientHumidityMinimum OBJECT-TYPE
    SYNTAX      TenthInteger32 (0..1000)
    MAX-ACCESS  read-only
    STATUS      current
    DESCRIPTION
        "Minimum relative humidity seen (percent). I.e. 13."
    ::= { nutAmbientEntry 12 }

-- Name                           Description                                                            Example value
-- outlet.n.id                    Outlet system identifier (opaque string)                               1         
-- outlet.n.desc                  Outlet description (opaque string)                                     Main outlet
-- outlet.n.switch                Outlet switch control (on/off)                                         on        
-- outlet.n.status                Outlet switch status (on/off)                                          on        
-- outlet.n.switchable            Outlet switch ability (yes/no)                                         yes       
-- outlet.n.autoswitch.charge.low Remaining battery level to power off this outlet (percent)             80        
-- outlet.n.delay.shutdown        Interval to wait before shutting down this outlet (seconds)            180       
-- outlet.n.delay.start           Interval to wait before restarting this outlet (seconds)               120       
-- outlet.n.current               Current (A)                                                            0.19      
-- outlet.n.current.maximum       Maximum seen current (A)                                               0.56      
-- outlet.n.realpower             Current value of real power (W)                                        28        
-- outlet.n.voltage               Voltage (V)                                                            247.0     
-- outlet.n.powerfactor           Power Factor (dimensionless value between 0 and 1)                     0.85      
-- outlet.n.crestfactor           Crest Factor (dimensionless, equal to or greater than 1)               1.41      
-- outlet.n.power                 Apparent power (VA)                                                    46        

nutOutletTable     OBJECT-TYPE
    SYNTAX      SEQUENCE OF NutOutletEntryType
    MAX-ACCESS      not-accessible
    STATUS          current
    DESCRIPTION
         "A list of nutOutlet."
    ::= { nutMIBObjects 7 }

NutOutletEntryType ::=
    SEQUENCE {
       nutOutletIndex NutOutletIndexType,
       nutOutletId DisplayString,
       nutOutletDesc DisplayString,
       nutOutletSwitch INTEGER,
       nutOutletStatus INTEGER,
       nutOutletSwitchable INTEGER,
       nutOutletAutoswitchChargeLow Integer32,
       nutOutletDelayShutdown Integer32,
       nutOutletDelayStart Integer32,
       nutOutletCurrent HundredthInteger32,
       nutOutletCurrentMaximum HundredthInteger32,
       nutOutletRealpower Integer32,
       nutOutletVoltage TenthInteger32,
       nutOutletPowerfactor HundredthInteger32,
       nutOutletCrestfactor HundredthInteger32,
       nutOutletPower Integer32
    }

nutOutletEntry OBJECT-TYPE
    SYNTAX      NutOutletEntryType
    MAX-ACCESS  not-accessible
    STATUS      current
    DESCRIPTION
            "An entry containing information about a particular outlet."
    INDEX   { nutDeviceIndex, nutOutletIndex }
    ::= { nutOutletTable 1 }

nutOutletIndex OBJECT-TYPE
	SYNTAX      NutOutletIndexType
	MAX-ACCESS  not-accessible
	STATUS      current
	DESCRIPTION
            "A unique value, greater than or equal to zero, for each outlet. It stands for the outlet index.
            A special case is 0 which represents the whole set of outlets of the device."
    ::= { nutOutletEntry 1 }

nutOutletId OBJECT-TYPE
    SYNTAX      DisplayString (SIZE (0..255))
    MAX-ACCESS  read-only
    STATUS      current
    DESCRIPTION
        "Outlet system identifier (opaque string). I.e. 1."
    ::= { nutOutletEntry 2 }

nutOutletDesc OBJECT-TYPE
    SYNTAX      DisplayString (SIZE (0..255))
    MAX-ACCESS  read-only
    STATUS      current
    DESCRIPTION
        "Outlet description (opaque string). I.e. Main outlet."
    ::= { nutOutletEntry 3 }

nutOutletSwitch OBJECT-TYPE
    SYNTAX      INTEGER { off(0), on(1) }
    MAX-ACCESS  read-only
    STATUS      current
    DESCRIPTION
        "Outlet switch control (on/off). I.e. on."
    ::= { nutOutletEntry 4 }

nutOutletStatus OBJECT-TYPE
    SYNTAX      INTEGER { off(0), on(1) }
    MAX-ACCESS  read-only
    STATUS      current
    DESCRIPTION
        "Outlet switch status (on/off). I.e. on."
    ::= { nutOutletEntry 5 }

nutOutletSwitchable OBJECT-TYPE
    SYNTAX      INTEGER { no(0), yes(1) }
    MAX-ACCESS  read-only
    STATUS      current
    DESCRIPTION
        "Outlet switch ability (yes/no). I.e. yes."
    ::= { nutOutletEntry 6 }

nutOutletAutoswitchChargeLow OBJECT-TYPE
    SYNTAX      Integer32 (0..2147483647)
    MAX-ACCESS  read-only
    STATUS      current
    DESCRIPTION
        "Remaining battery level to power off this outlet (percent). I.e. 80."
    ::= { nutOutletEntry 7 }

nutOutletDelayShutdown OBJECT-TYPE
    SYNTAX      Integer32 (0..2147483647)
    MAX-ACCESS  read-only
    STATUS      current
    DESCRIPTION
        "Interval to wait before shutting down this outlet (seconds). I.e. 180."
    ::= { nutOutletEntry 8 }

nutOutletDelayStart OBJECT-TYPE
    SYNTAX      Integer32 (-1..2147483647)
    MAX-ACCESS  read-only
    STATUS      current
    DESCRIPTION
        "Interval to wait before restarting this outlet (seconds). I.e. 120."
    ::= { nutOutletEntry 9 }

nutOutletCurrent OBJECT-TYPE
    SYNTAX      HundredthInteger32 (0..2147483647)
    MAX-ACCESS  read-only
    STATUS      current
    DESCRIPTION
        "Current (0.01 A). I.e. 19 (0.19 A)."
    ::= { nutOutletEntry 10 }

nutOutletCurrentMaximum OBJECT-TYPE
    SYNTAX      HundredthInteger32 (0..2147483647)
    MAX-ACCESS  read-only
    STATUS      current
    DESCRIPTION
        "Maximum seen current (0.01 A). I.e. 56 (0.56 A)."
    ::= { nutOutletEntry 11 }

nutOutletRealpower OBJECT-TYPE
    SYNTAX      Integer32 (0..2147483647)
    MAX-ACCESS  read-only
    STATUS      current
    DESCRIPTION
        "Current value of real power (W). I.e. 28."
    ::= { nutOutletEntry 12 }

nutOutletVoltage OBJECT-TYPE
    SYNTAX      TenthInteger32 (0..2147483647)
    MAX-ACCESS  read-only
    STATUS      current
    DESCRIPTION
        "Voltage (0.1 V). I.e. 2470 (247 V)."
    ::= { nutOutletEntry 13 }

nutOutletPowerfactor OBJECT-TYPE
    SYNTAX      HundredthInteger32 (0..100)
    MAX-ACCESS  read-only
    STATUS      current
    DESCRIPTION
        "Power Factor (dimensionless value between 0 and 1, multiplied by 100). I.e. 85 (0.85)."
    ::= { nutOutletEntry 14 }

nutOutletCrestfactor OBJECT-TYPE
    SYNTAX      HundredthInteger32 (1..2147483647)
    MAX-ACCESS  read-only
    STATUS      current
    DESCRIPTION
        "Crest Factor (dimensionless, equal to or greater than 1, multiplied by 100). I.e. 141 (1.41)."
    ::= { nutOutletEntry 15 }

nutOutletPower OBJECT-TYPE
    SYNTAX      Integer32 (0..2147483647)
    MAX-ACCESS  read-only
    STATUS      current
    DESCRIPTION
        "Apparent power (VA). I.e. 46."
    ::= { nutOutletEntry 16 }

-- Name                           Description                                                            Example value
-- driver.name                    Driver name                                                            usbhid-ups
-- driver.version                 Driver version (NUT release)                                           X.Y.Z     
-- driver.version.internal        Internal driver version (if tracked separately)                        1.23.45   
-- driver.parameter.xxx           Parameter xxx (ups.conf or cmdline -x) setting                         (varies)  
-- driver.flag.xxx                Flag xxx (ups.conf or cmdline -x) status                               enabled (or absent)

nutDriverTable     OBJECT-TYPE
    SYNTAX      SEQUENCE OF NutDriverEntryType
    MAX-ACCESS      not-accessible
    STATUS          current
    DESCRIPTION
         "A list of drivers."
    ::= { nutMIBObjects 8 }

NutDriverEntryType ::=
    SEQUENCE {
       nutDriverName DisplayString,
       nutDriverVersion DisplayString,
       nutDriverVersionInternal DisplayString
    }

nutDriverEntry OBJECT-TYPE
    SYNTAX      NutDriverEntryType
    MAX-ACCESS  not-accessible
    STATUS      current
    DESCRIPTION
            "An entry containing information about a particular driver."
    INDEX   { nutDeviceIndex }
    ::= { nutDriverTable 1 }

nutDriverName OBJECT-TYPE
    SYNTAX      DisplayString (SIZE (0..255))
    MAX-ACCESS  read-only
    STATUS      current
    DESCRIPTION
        "Driver name. I.e. usbhid-ups."
    ::= { nutDriverEntry 1 }

nutDriverVersion OBJECT-TYPE
    SYNTAX      DisplayString (SIZE (0..255))
    MAX-ACCESS  read-only
    STATUS      current
    DESCRIPTION
        "Driver version (NUT release). I.e. X.Y.Z."
    ::= { nutDriverEntry 2 }

nutDriverVersionInternal OBJECT-TYPE
    SYNTAX      DisplayString (SIZE (0..255))
    MAX-ACCESS  read-only
    STATUS      current
    DESCRIPTION
        "Internal driver version (if tracked separately). I.e. 1.23.45."
    ::= { nutDriverEntry 3 }

--driverParameterXxx OBJECT-TYPE
--    SYNTAX      DisplayString (SIZE (0..255))
--    MAX-ACCESS  read-only
--    STATUS      current
--    DESCRIPTION
--        "Parameter xxx (ups.conf or cmdline -x) setting. I.e. (varies)."
--    ::= { driverEntry 4 }

--driverFlagXxx OBJECT-TYPE
--    SYNTAX      DisplayString (SIZE (0..255))
--    MAX-ACCESS  read-only
--    STATUS      current
--    DESCRIPTION
--        "Flag xxx (ups.conf or cmdline -x) status. I.e. enabled (or absent)."
--    ::= { driverEntry 5 }

-- Name                           Description                                                            Example value
-- server.info                    Server information                                                     Network UPS Tools upsd vX.Y.Z - http://www.networkupstools.org/
-- server.version                 Server version                                                         X.Y.Z     
nutServerObjects   OBJECT IDENTIFIER ::= { nutMIBObjects 9 }

nutServerInfo OBJECT-TYPE
    SYNTAX      DisplayString (SIZE (0..255))
    MAX-ACCESS  read-only
    STATUS      current
    DESCRIPTION
        "Server information. I.e. Network UPS Tools upsd vX.Y.Z - http://www.networkupstools.org/."
    ::= { nutServerObjects 1 }

nutServerVersion OBJECT-TYPE
    SYNTAX      DisplayString (SIZE (0..255))
    MAX-ACCESS  read-only
    STATUS      current
    DESCRIPTION
        "Server version. I.e. X.Y.Z."
    ::= { nutServerObjects 2 }

nutThreephaseTable     OBJECT-TYPE
    SYNTAX          SEQUENCE OF ThreephaseEntryType
    MAX-ACCESS      not-accessible
    STATUS          current
    DESCRIPTION
         "A list of three-phase device information."
    ::= { nutMIBObjects 10 }
   
ThreephaseEntryType ::=
    SEQUENCE {
       nutThreephaseDomain INTEGER,
       nutThreephaseSubdomain INTEGER,
       nutThreephaseContext INTEGER,
       nutThreephaseCurrent HundredthInteger32,
       nutThreephaseCurrentMaximum HundredthInteger32,
       nutThreephaseCurrentMinimum HundredthInteger32,
       nutThreephaseCurrentPeak HundredthInteger32,
       nutThreephaseVoltage TenthInteger32,
       nutThreephaseVoltageNominal TenthInteger32,
       nutThreephaseVoltageMaximum TenthInteger32,
       nutThreephaseVoltageMinimum TenthInteger32,
       nutThreephasePower Integer32,
       nutThreephasePowerMaximum Integer32,
       nutThreephasePowerMinimum Integer32,
       nutThreephasePowerPercent Integer32,
       nutThreephasePowerPercentMaximum Integer32,
       nutThreephasePowerPercentMinimum Integer32,
       nutThreephaseRealpower Integer32,
       nutThreephasePowerfactor HundredthInteger32,
       nutThreephaseCrestfactor HundredthInteger32,
       nutThreephaseFrequency TenthInteger32,
       nutThreephaseFrequencyNominal TenthInteger32
    }
    
nutThreephaseEntry OBJECT-TYPE
    SYNTAX      ThreephaseEntryType
    MAX-ACCESS  not-accessible
    STATUS      current
    DESCRIPTION
            "An entry containing information about a particular driver."
    INDEX   { nutDeviceIndex, nutThreephaseDomain, nutThreephaseSubdomain, nutThreephaseContext }
    ::= { nutThreephaseTable 1 }
   
nutThreephaseDomain OBJECT-TYPE
    SYNTAX       INTEGER { input(1), output(2) }
    MAX-ACCESS   not-accessible
    STATUS       current
    DESCRIPTION
            "In a three-phased device, this type defines if the measure is about the 
             input or output." 
    ::= { nutThreephaseEntry 1 }        

nutThreephaseSubdomain OBJECT-TYPE
    SYNTAX       INTEGER { mains(1), bypass(2), servicebypass(3), load(4), inverter(5) }    
    MAX-ACCESS   not-accessible
    STATUS       current
    DESCRIPTION
            "In a three-phased device, in combination with DomainType, this type completes
             the measure context. 'mains' (input.mains.) is only for input and is equals to 'input.'.
             'load' (output.load.) is only for output and is equals to 'output.'. inverter is also
             only for output." 
    ::= { nutThreephaseEntry 2 }        

nutThreephaseContext OBJECT-TYPE
    SYNTAX       INTEGER { none(0), n(1), l1(2), l2(3), l3(4), l1n(5), l2n(6), l3n(7), l1l2(8), l2l3(9), l3l1(10) }
    MAX-ACCESS   not-accessible
    STATUS       current
    DESCRIPTION
            "In a three-phased device, the naming scheme becomes DOMAIN.CONTEXT.SPEC when in
             three-phase mode. Example: input.L1.current. 'none' means the absence of context,
             for frequency related measures and aggregated/averaged ones"
    ::= { nutThreephaseEntry 3 }

nutThreephaseCurrent OBJECT-TYPE
    SYNTAX      HundredthInteger32 (0..2147483647)
    MAX-ACCESS  read-only
    STATUS      current
    DESCRIPTION
        "Current (0.01 A). I.e. 19 (0.19 A)."
    ::= { nutThreephaseEntry 4 }

nutThreephaseCurrentMaximum OBJECT-TYPE
    SYNTAX      HundredthInteger32 (0..2147483647)
    MAX-ACCESS  read-only
    STATUS      current
    DESCRIPTION
        "Maximum seen current (0.01 A). I.e. 56 (0.56 A)."
    ::= { nutThreephaseEntry 5 }

nutThreephaseCurrentMinimum OBJECT-TYPE
    SYNTAX      HundredthInteger32 (0..2147483647)
    MAX-ACCESS  read-only
    STATUS      current
    DESCRIPTION
        "Minimum seen current (0.01 A). I.e. 56 (0.56 A)."
    ::= { nutThreephaseEntry 6 }

nutThreephaseCurrentPeak OBJECT-TYPE
    SYNTAX      HundredthInteger32 (0..2147483647)
    MAX-ACCESS  read-only
    STATUS      current
    DESCRIPTION
        "Peak current (0.01 A). I.e. 56 (0.56 A)."
    ::= { nutThreephaseEntry 7 }    
    
nutThreephaseVoltage OBJECT-TYPE
    SYNTAX      TenthInteger32 (0..2147483647)
    MAX-ACCESS  read-only
    STATUS      current
    DESCRIPTION
        "Voltage (0.1 V). I.e. 2470 (247 V)."
    ::= { nutThreephaseEntry 8 }

nutThreephaseVoltageNominal OBJECT-TYPE
    SYNTAX      TenthInteger32 (0..2147483647)
    MAX-ACCESS  read-only
    STATUS      current
    DESCRIPTION
        "Nominal voltage (0.1 V). I.e. 2470 (247 V)."
    ::= { nutThreephaseEntry 9 }

nutThreephaseVoltageMaximum OBJECT-TYPE
    SYNTAX      TenthInteger32 (0..2147483647)
    MAX-ACCESS  read-only
    STATUS      current
    DESCRIPTION
        "Maximum seen voltage (0.1 V). I.e. 2470 (247 V)."
    ::= { nutThreephaseEntry 10 }

nutThreephaseVoltageMinimum OBJECT-TYPE
    SYNTAX      TenthInteger32 (0..2147483647)
    MAX-ACCESS  read-only
    STATUS      current
    DESCRIPTION
        "Minimum seen voltage (0.1 V). I.e. 2470 (247 V)."
    ::= { nutThreephaseEntry 11 }
    
nutThreephasePower OBJECT-TYPE
    SYNTAX      Integer32 (0..2147483647)
    MAX-ACCESS  read-only
    STATUS      current
    DESCRIPTION
        "Apparent power (VA). I.e. 46."
    ::= { nutThreephaseEntry 12 }       

nutThreephasePowerMaximum OBJECT-TYPE
    SYNTAX      Integer32 (0..2147483647)
    MAX-ACCESS  read-only
    STATUS      current
    DESCRIPTION
        "Maximum seen apparent power (VA). I.e. 46."
    ::= { nutThreephaseEntry 13 }      
    
nutThreephasePowerMinimum OBJECT-TYPE
    SYNTAX      Integer32 (0..2147483647)
    MAX-ACCESS  read-only
    STATUS      current
    DESCRIPTION
        "Minimum seen apparent power (VA). I.e. 46."
    ::= { nutThreephaseEntry 14 }          

nutThreephasePowerPercent OBJECT-TYPE
    SYNTAX      Integer32 (0..100)
    MAX-ACCESS  read-only
    STATUS      current
    DESCRIPTION
        "Percentage of apparent power related to maximum load (percent). I.e. 023."
    ::= { nutThreephaseEntry 15 }    

nutThreephasePowerPercentMaximum OBJECT-TYPE
    SYNTAX      Integer32 (0..100)
    MAX-ACCESS  read-only
    STATUS      current
    DESCRIPTION
        "Max seen percentage of apparent power (percent). I.e. 023."
    ::= { nutThreephaseEntry 16 }    
    
nutThreephasePowerPercentMinimum OBJECT-TYPE
    SYNTAX      Integer32 (0..100)
    MAX-ACCESS  read-only
    STATUS      current
    DESCRIPTION
        "Min seen percentage of apparent power (percent). I.e. 023."
    ::= { nutThreephaseEntry 17 }            
    
nutThreephaseRealpower OBJECT-TYPE
    SYNTAX      Integer32 (0..2147483647)
    MAX-ACCESS  read-only
    STATUS      current
    DESCRIPTION
        "Current value of real power (W). I.e. 28."
    ::= { nutThreephaseEntry 18 }    
    
nutThreephasePowerfactor OBJECT-TYPE
    SYNTAX      HundredthInteger32 (0..100)
    MAX-ACCESS  read-only
    STATUS      current
    DESCRIPTION
        "Power Factor (dimensionless value between 0 and 1, multiplied by 100). I.e. 85 (0.85)."
    ::= { nutThreephaseEntry 19 }

nutThreephaseCrestfactor OBJECT-TYPE
    SYNTAX      HundredthInteger32 (1..2147483647)
    MAX-ACCESS  read-only
    STATUS      current
    DESCRIPTION
        "Crest Factor (dimensionless, equal to or greater than 1, multiplied by 100). I.e. 141 (1.41)."
    ::= { nutThreephaseEntry 20 }    
    
nutThreephaseFrequency OBJECT-TYPE
    SYNTAX      TenthInteger32 (0..2147483647)
    MAX-ACCESS  read-only
    STATUS      current
    DESCRIPTION
        "Frequency (0.1 Hz). I.e. 602 (60.2 Hz)."
    ::= { nutThreephaseEntry 21 }

nutThreephaseFrequencyNominal OBJECT-TYPE
    SYNTAX      TenthInteger32 (0..2147483647)
    MAX-ACCESS  read-only
    STATUS      current
    DESCRIPTION
        "Nominal frequency (0.1 Hz). I.e. 600."
    ::= { nutThreephaseEntry 22 }
    
-- conformance information

nutConformance       OBJECT IDENTIFIER ::= { nutMIB 2 }
nutCompliances       OBJECT IDENTIFIER ::= { nutConformance 2 }

nutGroups            OBJECT IDENTIFIER ::= { nutConformance 1 }

nutCompliance1 MODULE-COMPLIANCE
    STATUS  current
    DESCRIPTION
            "The compliance statement for NUT devices."

    MODULE  -- this module
        MANDATORY-GROUPS { nutServerGroup }
        GROUP nutDeviceGroup
            DESCRIPTION
                "A collection of objects providing information specific to
                 a device"
        GROUP nutUpsGroup
            DESCRIPTION
                "A collection of objects providing information specific to
                 a device"
        GROUP nutInputGroup
            DESCRIPTION
                "A collection of objects providing information specific to
                 an input of a device"
        GROUP nutOutputGroup
            DESCRIPTION
                "A collection of objects providing information specific to
                 an output of a device"
        GROUP nutBatteryGroup
            DESCRIPTION
                "A collection of objects providing information specific to
                 a baterry of a device"
        GROUP nutAmbientGroup
            DESCRIPTION
                "A collection of objects providing information specific to
                 the ambient of a device"
        GROUP nutOutletGroup
            DESCRIPTION
                "A collection of objects providing information specific to
                 a outlet of a device"
        GROUP nutDriverGroup
            DESCRIPTION
                "A collection of objects providing information specific to
                 the driver of a device"
        GROUP nutServerGroup
            DESCRIPTION
                "A collection of objects providing information specific to
                 the server"
        GROUP nutThreephaseGroup
            DESCRIPTION
                "A collection of objects providing information specific to
                three-phased devices in three-phase mode"                 
    ::= { nutCompliances 1 }


nutDeviceGroup    OBJECT-GROUP
    OBJECTS { nutDeviceName, nutDeviceDesc, 
              nutDeviceModel, nutDeviceMfr, 
              nutDeviceSerial, nutDeviceType }
    STATUS  current
    DESCRIPTION
            "A collection of objects providing information specific to
             a device"
    ::= { nutGroups 1 }

nutUpsGroup    OBJECT-GROUP
    OBJECTS {
       nutUpsStatus, nutUpsAlarm, nutUpsTime,
       nutUpsDate, nutUpsModel, nutUpsMfr,
       nutUpsMfrDate, nutUpsSerial,
       nutUpsVendorid, nutUpsProductid,
       nutUpsFirmware, nutUpsFirmwareAux,
       nutUpsTemperature, nutUpsLoad,
       nutUpsLoadHigh, nutUpsId,
       nutUpsDelayStart, nutUpsDelayReboot,
       nutUpsDelayShutdown, nutUpsTimerStart,
       nutUpsTimerReboot, nutUpsTimerShutdown,
       nutUpsTestInterval, nutUpsTestResult,
       nutUpsDisplayLanguage, nutUpsContacts,
       nutUpsEfficiency, nutUpsPower,
       nutUpsPowerNominal, nutUpsRealpower,
       nutUpsRealpowerNominal, nutUpsBeeperStatus,
       nutUpsType, nutUpsWatchdogStatus,
       nutUpsStartAuto, nutUpsStartBattery,
       nutUpsStartReboot
    }
    STATUS  current
    DESCRIPTION
            "A collection of objects providing information specific to
             a device"
    ::= { nutGroups 2 }

nutInputGroup    OBJECT-GROUP
    OBJECTS {
       nutInputVoltage, nutInputVoltageMaximum,
       nutInputVoltageMinimum, nutInputVoltageNominal,
       nutInputVoltageExtended, nutInputTransferReason,
       nutInputTransferLow, nutInputTransferHigh,
       nutInputTransferLowMin, nutInputTransferLowMax,
       nutInputTransferHighMin, nutInputTransferHighMax,
       nutInputSensitivity, nutInputQuality,
       nutInputCurrent, nutInputCurrentNominal,
       nutInputFrequency, nutInputFrequencyNominal,
       nutInputFrequencyLow, nutInputFrequencyHigh,
       nutInputFrequencyExtended, nutInputTransferBoostLow,
       nutInputTransferBoostHigh, nutInputTransferTrimLow,
       nutInputTransferTrimHigh, nutInputPhases
    }
    STATUS  current
    DESCRIPTION
            "A collection of objects providing information specific to
             an input of a device"
    ::= { nutGroups 3 }

nutOutputGroup    OBJECT-GROUP
    OBJECTS {
       nutOutputVoltage, nutOutputVoltageNominal,
       nutOutputFrequency, nutOutputFrequencyNominal,
       nutOutputCurrent, nutOutputCurrentNominal,
       nutOutputPhases
    }
    STATUS  current
    DESCRIPTION
            "A collection of objects providing information specific to
             an output of a device"
    ::= { nutGroups 4 }

nutBatteryGroup    OBJECT-GROUP
    OBJECTS {
       nutBatteryCharge, nutBatteryChargeLow,
       nutBatteryChargeRestart, nutBatteryChargeWarning,
       nutBatteryVoltage, nutBatteryCapacity,
       nutBatteryCurrent, nutBatteryTemperature,
       nutBatteryVoltageNominal, nutBatteryRuntime,
       nutBatteryRuntimeLow, nutBatteryAlarmThreshold,
       nutBatteryDate, nutBatteryMfrDate,
       nutBatteryPacks, nutBatteryPacksBad,
       nutBatteryType, nutBatteryProtection,
       nutBatteryEnergysave
    }
    STATUS  current
    DESCRIPTION
            "A collection of objects providing information specific to
             a baterry of a device"
    ::= { nutGroups 5 }

nutAmbientGroup    OBJECT-GROUP
    OBJECTS {
       nutAmbientTemperature,
       nutAmbientTemperatureAlarm,
       nutAmbientTemperatureHigh,
       nutAmbientTemperatureLow,
       nutAmbientTemperatureMaximum,
       nutAmbientTemperatureMinimum,
       nutAmbientHumidity,
       nutAmbientHumidityAlarm,
       nutAmbientHumidityHigh,
       nutAmbientHumidityLow,
       nutAmbientHumidityMaximum,
       nutAmbientHumidityMinimum
    }
    STATUS  current
    DESCRIPTION
            "A collection of objects providing information specific to
             the ambient of a device"
    ::= { nutGroups 6 }

nutOutletGroup    OBJECT-GROUP
    OBJECTS {
       nutOutletId,
       nutOutletDesc,
       nutOutletSwitch,
       nutOutletStatus,
       nutOutletSwitchable,
       nutOutletAutoswitchChargeLow,
       nutOutletDelayShutdown,
       nutOutletDelayStart,
       nutOutletCurrent,
       nutOutletCurrentMaximum,
       nutOutletRealpower,
       nutOutletVoltage,
       nutOutletPowerfactor,
       nutOutletCrestfactor,
       nutOutletPower
    }
    STATUS  current
    DESCRIPTION
            "A collection of objects providing information specific to
             a outlet of a device"
    ::= { nutGroups 7 }

nutDriverGroup    OBJECT-GROUP
    OBJECTS {
       nutDriverName,
       nutDriverVersion,
       nutDriverVersionInternal
   }
    STATUS  current
    DESCRIPTION
            "A collection of objects providing information specific to
             the driver of a device"
    ::= { nutGroups 8 }

nutServerGroup    OBJECT-GROUP
    OBJECTS {
        nutServerInfo, nutServerVersion
    }
    STATUS  current
    DESCRIPTION
            "A collection of objects providing information specific to
             the server"
    ::= { nutGroups 9 }

nutThreephaseGroup    OBJECT-GROUP
    OBJECTS {
        nutThreephaseCurrent, nutThreephaseCurrentMaximum, nutThreephaseCurrentMinimum,
        nutThreephaseCurrentPeak, nutThreephaseVoltage, nutThreephaseVoltageNominal,
        nutThreephaseVoltageMaximum, nutThreephaseVoltageMinimum, nutThreephasePower,
        nutThreephasePowerMaximum, nutThreephasePowerMinimum, nutThreephasePowerPercent, 
        nutThreephasePowerPercentMaximum, nutThreephasePowerPercentMinimum,
        nutThreephaseRealpower, nutThreephasePowerfactor, nutThreephaseCrestfactor,
        nutThreephaseFrequency, nutThreephaseFrequencyNominal
    }
    STATUS  current
    DESCRIPTION
            "A collection of objects providing information specific to
             three-phased devices in three-phase mode"
    ::= { nutGroups 10 }    
    
END
